module sonic-tc-priority-group-map {
    namespace "http://github.com/Azure/sonic-tc-priority-group-map";
    prefix tpg;

    import sonic-extension {
        prefix sonic-ext;
    }

    organization
        "SONiC";

    contact
        "SONiC";

    description
        "SONIC TC_TO_PRIORITY_GROUP_MAP";

    revision 2021-04-15 {
        description
            "Initial revision.";
    }

    container sonic-tc-priority-group-map {

        container TC_TO_PRIORITY_GROUP_MAP {

            list TC_TO_PRIORITY_GROUP_MAP_LIST {
                key "name";
                //sonic-ext:map-list "true"; //special conversion for map tables
                //sonic-ext:map-leaf "tc_num pg_num"; //every key:value pair is mapped to list keys, e.g. "1":"7" ==> tc_num=1, dscp=7

                leaf name {
                    type string {
                        pattern '[a-zA-Z0-9]{1}([-a-zA-Z0-9_]{0,31})';
                        length 1..32;
                    }
                }

                list TC_TO_PRIORITY_GROUP_MAP { //this is list inside list for storing mapping between two fields
                    key "tc_num pg_num";

                    leaf tc_num {
                        type string {
                            pattern "[0-9]?";
                        }
                    }

                    leaf pg_num {
                        type string {
                            pattern "[0-7]?";
                        }
                    }
                }
            }
        }
    }
}
